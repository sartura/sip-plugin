module sip {

    namespace "urn:opencpe:sip";

    prefix "ocpe-sip";

    organization
        "Deutsche Telekom AG";

    contact
        "Landgrabenweg 151
        53227 Bonn, Germany";

    description
        "This module defines SIP used in the TeraStream home gateway project.";

    revision "2017-08-09" {
        description
            "Version 0.2.0";
    }

	container sip-config {
		description
		 "Configuration for SIP.";

		list sip-account {
			description
			 "Sip account.";

			key account;

			leaf enabled {
				 description "Enable this account";
				type boolean;
				default "true";
			}
			leaf account {
				 description "Name of the SIP account";
				type string;
			}
			leaf account_name {
				 description "Name of the account";
				type string;
				mandatory true;
			}
			leaf domain {
				 description "SIP doamin name";
				type string;
				mandatory true;
			}
			leaf username {
				 description "username";
				type string;
				mandatory true;
			}
			leaf password {
				 description "password";
				type string;
				mandatory true;
			}
			leaf authentication_name {
				 description "Name used for authentication on SIP server";
				type string;
				mandatory true;
			}
			leaf display_name {
				 description "Display name used in Caller Id";
				type string;
				mandatory true;
			}
			container server {
				leaf registrar {
					 description "SIP server registrar";
					type string;
				}
				leaf registrar_port {
					 description "SIP server registrar port";
					type uint32;
				}
			}
			container outbound_proxy {
				leaf proxy {
					 description "SIP outbound proxy";
					type string;
				}
				leaf port {
					 description "SIP outbound proxy port";
					type uint32;
				}
			}
		}
		list sip-user {
			description
			 "Sip user account.";

			key sip_user;

			leaf enabled {
				 description "Enable this user account";
				type boolean;
				default "true";
			}
			leaf sip_user {
				 description "Name of the SIP user account";
				type string;
			}
			leaf extension {
				 description "SIP doamin name";
				type uint32;
				mandatory true;
			}
			leaf username {
				 description "username";
				type string;
				mandatory true;
			}
			leaf password {
				 description "password";
				type string;
				mandatory true;
			}

		}
	}

    rpc start {
        description
            "Start SIP deamon.";
    }

    rpc stop {
        description
            "Stop SIP deamon.";
    }

    rpc restart {
        description
            "Restart SIP deamon.";
    }

    rpc reload {
        description
            "Reload SIP configuration files (or restart if that fails).";
    }

    rpc disable {
        description
            "Disable SIP deamon autostart.";
    }

    rpc enable {
        description
            "Enable SIP deamon autostart.";
    }
}
